#!/usr/bin/env python
#
# Python 2 compatible version of EvaluateFile.FCMacro for FreeCAD 0.14-0.17.
#
# Produces the same schema v4 JSON output as the main macro, but avoids:
#   - Type annotations (-> bool, : str)
#   - f-strings
#   - from __future__ imports beyond what Python 2.7 supports
#   - APIs added after FreeCAD 0.17 (e.g. DocumentObject.isValid())
#
# Usage:
#   freecadcmd EvaluateFilePy2.FCMacro /path/to/model.FCStd --out results.json

import datetime
import platform
import sys
import os
import json
import argparse

import FreeCAD as App


def is_obj_valid(obj):
    """Check whether a FreeCAD document object is valid.

    Falls back to True on older FreeCAD where isValid() does not exist.
    Use this for gate checks (should we analyze this object?).
    """
    try:
        return obj.isValid()
    except AttributeError:
        return True


def report_obj_valid(obj):
    """Report whether a FreeCAD document object is valid, for recording as a metric.

    Returns None on older FreeCAD where isValid() does not exist, so the
    comparison logic can distinguish "unknown" from a definite True/False.
    """
    # An object that did not recompute cleanly is reported as invalid: its
    # shape is stale on-disk geometry rather than a recompute result.
    if not recompute_clean(obj):
        return False
    try:
        return obj.isValid()
    except AttributeError:
        return None


def is_shape_valid(shape):
    """Check whether a FreeCAD shape is non-null and geometrically valid."""
    try:
        return (shape is not None) and (not shape.isNull()) and shape.isValid()
    except Exception:
        return False


# Construction/datum object types carry no measured solid geometry. They are
# frequently left "Invalid" after a load+recompute (App::Origin especially)
# without affecting the solids we measure, so they must NOT count as a recompute
# failure when judging whether a shape is trustworthy.
_CONSTRUCTION_TYPE_IDS = set(
    [
        "App::Origin",
        "App::Line",
        "App::Plane",
        "App::Axis",
        "App::OriginFeature",
        "PartDesign::CoordinateSystem",
        "PartDesign::Plane",
        "PartDesign::Line",
        "PartDesign::Point",
    ]
)


def _is_construction(obj):
    """True if obj is a datum/origin construction object with no measured solid."""
    tid = getattr(obj, "TypeId", "") or ""
    return tid in _CONSTRUCTION_TYPE_IDS or "Datum" in tid or "Origin" in tid


def _object_failed_recompute(obj):
    """True if obj's own State shows a real, geometry-relevant recompute failure.

    Construction/datum objects are ignored: an Invalid Origin or local
    coordinate system does not make the solids built in the document stale.
    """
    if _is_construction(obj):
        return False
    try:
        state = list(obj.State)
    except Exception:
        return False
    return ("Invalid" in state) or ("Error" in state)


def recompute_clean(obj):
    """Return True if a reported object's shape is a trustworthy recompute result.

    When a geometry feature fails to execute (e.g. a pre-1.0 PartDesign feature
    with no Body raising "Missing container body", or a sketch that no longer
    solves), FreeCAD aborts the recompute chain: the failed feature is marked
    Invalid/Error and downstream objects are left Touched while still exposing
    the geometry loaded from the saved file.  Walk the object together with its
    transitive dependencies (OutList) and report it untrustworthy if any
    geometry-producing object in that closure failed to recompute.  Merely
    Touched objects with no failed dependency (static Part::Feature imports, or
    App::Part containers whose only invalid child is an Origin) are trustworthy.
    """
    seen = set()
    stack = [obj]
    while stack:
        cur = stack.pop()
        name = getattr(cur, "Name", None)
        if name in seen:
            continue
        seen.add(name)
        if _object_failed_recompute(cur):
            return False
        try:
            stack.extend(list(cur.OutList))
        except Exception:
            pass
    return True


def get_solids_from_shape(shape):
    """Extract all solid sub-shapes from a FreeCAD shape."""
    try:
        solids = list(shape.Solids)
        if solids:
            return solids
    except Exception:
        pass
    try:
        if getattr(shape, "ShapeType", "") == "Solid":
            return [shape]
    except Exception:
        pass
    return []


def get_freecad_version_string():
    """Return a human-readable FreeCAD version string."""
    try:
        v = App.Version()
        return ".".join(v[:3]) + (" " + v[3] if len(v) > 3 else "")
    except Exception:
        return "unknown"


# TypeIds that have a Shape but are non-solid construction geometry
_NON_SOLID_TYPES = set(
    [
        "PartDesign::Line",
        "PartDesign::Plane",
        "PartDesign::Point",
        "PartDesign::CoordinateSystem",
        "PartDesign::ShapeBinder",
        "PartDesign::SubShapeBinder",
        "Sketcher::SketchObject",
        # Body's shape duplicates its tip; App::Part aggregates children.
        "PartDesign::Body",
        "App::Part",
    ]
)

_PD_SKIP_TYPES = set(
    [
        "PartDesign::Line",
        "PartDesign::Plane",
        "PartDesign::Point",
        "PartDesign::CoordinateSystem",
        "PartDesign::ShapeBinder",
        "PartDesign::SubShapeBinder",
    ]
)


def _source_dict(obj):
    """Build the _source annotation dict for an object."""
    return {
        "_source_name": obj.Name,
        "_source_label": getattr(obj, "Label", obj.Name),
        "_source_type_id": getattr(obj, "TypeId", "unknown"),
    }


def evaluate_shape(obj):
    """Compute aggregate solid metrics for an object's shape."""
    result = _source_dict(obj)

    # A final solid that did not recompute cleanly is reporting the shape loaded
    # from the saved file, not a recomputed result -- treat it as invalid.
    if not recompute_clean(obj):
        result["metrics"] = {"is_valid": False}
        return result

    if not is_obj_valid(obj) or not hasattr(obj, "Shape") or not is_shape_valid(obj.Shape):
        result["metrics"] = {"is_valid": False}
        return result

    shape = obj.Shape
    solids = get_solids_from_shape(shape)
    if not solids:
        result["metrics"] = {"is_valid": False}
        return result

    try:
        valid_solids = [s for s in solids if is_shape_valid(s)]
        total_volume = sum(float(s.Volume) for s in valid_solids)
        metrics = {
            "is_valid": True,
            "solid_count": len(solids),
            "total_volume_mm3": total_volume,
            "total_area_mm2": float(shape.Area),
            "bounding_box": {
                "x_min": float(shape.BoundBox.XMin),
                "y_min": float(shape.BoundBox.YMin),
                "z_min": float(shape.BoundBox.ZMin),
                "x_max": float(shape.BoundBox.XMax),
                "y_max": float(shape.BoundBox.YMax),
                "z_max": float(shape.BoundBox.ZMax),
            },
        }
        try:
            com = shape.CenterOfMass
            metrics["center_of_mass"] = {
                "x": float(com.x),
                "y": float(com.y),
                "z": float(com.z),
            }
        except AttributeError:
            if total_volume > 0 and valid_solids:
                wx = sum(float(s.CenterOfMass.x) * float(s.Volume) for s in valid_solids)
                wy = sum(float(s.CenterOfMass.y) * float(s.Volume) for s in valid_solids)
                wz = sum(float(s.CenterOfMass.z) * float(s.Volume) for s in valid_solids)
                metrics["center_of_mass"] = {
                    "x": wx / total_volume,
                    "y": wy / total_volume,
                    "z": wz / total_volume,
                }
    except Exception:
        metrics = {"is_valid": False}

    result["metrics"] = metrics
    return result


def analyze_sketch(obj):
    """Analyze a Sketcher::SketchObject.  Returns an entry dict, or None."""
    if getattr(obj, "TypeId", "") != "Sketcher::SketchObject":
        return None
    try:
        metrics = {
            "is_valid": report_obj_valid(obj),
            "constraint_count": int(getattr(obj, "ConstraintCount", 0)),
            "geometry_count": int(getattr(obj, "GeometryCount", 0)),
        }
        try:
            metrics["external_geometry_count"] = len(obj.ExternalGeometry)
        except Exception:
            metrics["external_geometry_count"] = 0
    except Exception:
        metrics = {"is_valid": False}
    return dict(_source_dict(obj), metrics=metrics)


def analyze_pd_body(obj):
    """Analyze a PartDesign::Body.  Returns an entry dict, or None."""
    if getattr(obj, "TypeId", "") != "PartDesign::Body":
        return None
    try:
        metrics = {"is_valid": report_obj_valid(obj)}
        group = getattr(obj, "Group", [])
        metrics["feature_count"] = len(group)
        tip = getattr(obj, "Tip", None)
        if tip is not None:
            metrics["tip_name"] = tip.Name
            metrics["tip_is_valid"] = is_obj_valid(tip)
        else:
            metrics["tip_name"] = None
            metrics["tip_is_valid"] = False
    except Exception:
        metrics = {"is_valid": False}
    return dict(_source_dict(obj), metrics=metrics)


def analyze_pd_feature(obj):
    """Analyze a PartDesign feature.  Returns an entry dict, or None."""
    tid = getattr(obj, "TypeId", "")
    if not tid.startswith("PartDesign::"):
        return None
    if tid == "PartDesign::Body" or tid in _PD_SKIP_TYPES:
        return None
    if not hasattr(obj, "Shape"):
        return None
    try:
        metrics = {"is_valid": report_obj_valid(obj)}
        shape = getattr(obj, "Shape", None)
        if shape is not None and is_shape_valid(shape):
            metrics["shape_type"] = shape.ShapeType
            # solid_count > 1 is a hard error on FreeCAD <= 1.0; allowed from 1.1 on.
            try:
                metrics["solid_count"] = len(get_solids_from_shape(shape))
            except Exception:
                pass
    except Exception:
        metrics = {"is_valid": False}
    return dict(_source_dict(obj), metrics=metrics)


def analyze_part_feature(obj):
    """Analyze a Part:: feature.  Returns an entry dict, or None.

    Records validity, shape type, shell closure, total volume / area, bounding
    box, center of mass, and Placement.Base. The geometric metrics let the test
    suite catch regressions where a Part::Feature's visible geometry is the same
    across versions but its internal coordinates / Placement diverge (see
    FreeCAD issue #29733 for the canonical case).
    """
    if not getattr(obj, "TypeId", "").startswith("Part::"):
        return None
    if not hasattr(obj, "Shape"):
        return None
    try:
        metrics = {"is_valid": report_obj_valid(obj)}
        shape = getattr(obj, "Shape", None)
        if shape is not None and is_shape_valid(shape):
            metrics["shape_type"] = shape.ShapeType
            try:
                shells = shape.Shells
                if shells:
                    metrics["shell_is_closed"] = all(shell.isClosed() for shell in shells)
            except Exception:
                pass
            try:
                base = shape.Placement.Base
                metrics["placement_base"] = {
                    "x": float(base.x),
                    "y": float(base.y),
                    "z": float(base.z),
                }
            except Exception:
                pass
            try:
                metrics["bounding_box"] = {
                    "x_min": float(shape.BoundBox.XMin),
                    "y_min": float(shape.BoundBox.YMin),
                    "z_min": float(shape.BoundBox.ZMin),
                    "x_max": float(shape.BoundBox.XMax),
                    "y_max": float(shape.BoundBox.YMax),
                    "z_max": float(shape.BoundBox.ZMax),
                }
            except Exception:
                pass
            try:
                metrics["total_area_mm2"] = float(shape.Area)
            except Exception:
                pass
            try:
                solids = get_solids_from_shape(shape)
                valid_solids = [s for s in solids if is_shape_valid(s)]
                if valid_solids:
                    total_volume = sum(float(s.Volume) for s in valid_solids)
                    metrics["total_volume_mm3"] = total_volume
                    try:
                        com = shape.CenterOfMass
                        metrics["center_of_mass"] = {
                            "x": float(com.x),
                            "y": float(com.y),
                            "z": float(com.z),
                        }
                    except AttributeError:
                        if total_volume > 0:
                            wx = sum(
                                float(s.CenterOfMass.x) * float(s.Volume) for s in valid_solids
                            )
                            wy = sum(
                                float(s.CenterOfMass.y) * float(s.Volume) for s in valid_solids
                            )
                            wz = sum(
                                float(s.CenterOfMass.z) * float(s.Volume) for s in valid_solids
                            )
                            metrics["center_of_mass"] = {
                                "x": wx / total_volume,
                                "y": wy / total_volume,
                                "z": wz / total_volume,
                            }
            except Exception:
                pass
    except Exception:
        metrics = {"is_valid": False}
    return dict(_source_dict(obj), metrics=metrics)


def analyze_app_part(obj):
    """Analyze an App::Part container.  Returns an entry dict, or None."""
    if getattr(obj, "TypeId", "") != "App::Part":
        return None
    try:
        metrics = {"is_valid": report_obj_valid(obj)}
        group = getattr(obj, "Group", [])
        metrics["child_count"] = len(group)
        shape = getattr(obj, "Shape", None)
        if shape is not None and is_shape_valid(shape):
            metrics["bounding_box"] = {
                "x_min": float(shape.BoundBox.XMin),
                "y_min": float(shape.BoundBox.YMin),
                "z_min": float(shape.BoundBox.ZMin),
                "x_max": float(shape.BoundBox.XMax),
                "y_max": float(shape.BoundBox.YMax),
                "z_max": float(shape.BoundBox.ZMax),
            }
    except Exception:
        metrics = {"is_valid": False}
    return dict(_source_dict(obj), metrics=metrics)


def analyze_spreadsheet(obj):
    """Analyze a Spreadsheet::Sheet.  Returns an entry dict, or None."""
    if getattr(obj, "TypeId", "") != "Spreadsheet::Sheet":
        return None
    try:
        metrics = {"is_valid": report_obj_valid(obj)}
        try:
            used_cells = obj.getUsedCells()
            metrics["cell_count"] = len(used_cells)
        except Exception:
            metrics["cell_count"] = -1
    except Exception:
        metrics = {"is_valid": False}
    return dict(_source_dict(obj), metrics=metrics)


def analyze_material(obj):
    """Analyze a material object.  Returns an entry dict, or None."""
    type_id = getattr(obj, "TypeId", "")
    if "Material" not in type_id:
        if not (hasattr(obj, "Material") and isinstance(getattr(obj, "Material", None), dict)):
            return None
    try:
        metrics = {"is_valid": report_obj_valid(obj)}
        material = getattr(obj, "Material", None)
        if isinstance(material, dict):
            if "Name" in material:
                metrics["material_name"] = str(material["Name"])
    except Exception:
        metrics = {"is_valid": False}
    return dict(_source_dict(obj), metrics=metrics)


# Non-solid analyzer functions and their section names.
ANALYZERS = [
    ("sketches", analyze_sketch),
    ("partdesign_bodies", analyze_pd_body),
    ("partdesign_features", analyze_pd_feature),
    ("part_features", analyze_part_feature),
    ("app_parts", analyze_app_part),
    ("spreadsheets", analyze_spreadsheet),
    ("materials", analyze_material),
]


def _find_final_solid_objects(doc):
    """Return only the top-level shape-producing objects in a document."""
    owned = set()
    for obj in doc.Objects:
        type_id = getattr(obj, "TypeId", "")
        if type_id in ("PartDesign::Body", "App::Part"):
            for child in getattr(obj, "Group", []):
                owned.add(child.Name)
                if getattr(child, "TypeId", "") == "PartDesign::Body":
                    for grandchild in getattr(child, "Group", []):
                        owned.add(grandchild.Name)

    consumed = set()
    for obj in doc.Objects:
        if not hasattr(obj, "Shape"):
            continue
        for dep in getattr(obj, "OutList", []):
            if hasattr(dep, "Shape"):
                consumed.add(dep.Name)

    skip_types = set(
        [
            "PartDesign::Line",
            "PartDesign::Plane",
            "PartDesign::Point",
            "PartDesign::CoordinateSystem",
            "PartDesign::ShapeBinder",
            "PartDesign::SubShapeBinder",
            "Sketcher::SketchObject",
            "App::Origin",
            "App::Line",
            "App::Plane",
            "App::DocumentObjectGroup",
        ]
    )

    finals = []
    for obj in doc.Objects:
        type_id = getattr(obj, "TypeId", "")
        if not hasattr(obj, "Shape"):
            continue
        if type_id in skip_types:
            continue
        if type_id in ("PartDesign::Body", "App::Part"):
            finals.append(obj)
            continue
        if obj.Name in owned:
            continue
        if obj.Name in consumed:
            continue
        shape = obj.Shape
        if not is_obj_valid(obj) or not is_shape_valid(shape):
            finals.append(obj)
            continue
        if shape.ShapeType in ("Vertex", "Edge", "Wire", "Face"):
            continue
        if get_solids_from_shape(shape):
            finals.append(obj)
    return finals


def scan_invalid_shapes(doc):
    """Scan every object for a geometrically invalid BRep Shape (OCCT BRepCheck).

    Catches latent invalid geometry that the file's native FreeCAD tolerates but stricter later
    versions reject.  Walks EVERY object, not just final solids: an intermediate feature can be
    shape.isValid() False while final solids, obj.isValid() and the recompute all report valid.
    Top-level list; the comparison harness ignores top-level keys.
    """
    invalid = []
    for obj in doc.Objects:
        shape = getattr(obj, "Shape", None)
        if shape is None:
            continue
        try:
            if shape.isNull() or shape.isValid():
                continue
        except Exception:
            continue
        try:
            obj_valid = obj.isValid()
        except Exception:
            obj_valid = None
        invalid.append(
            {
                "name": obj.Name,
                "label": getattr(obj, "Label", obj.Name),
                "type_id": obj.TypeId,
                "obj_valid": obj_valid,
            }
        )
    return invalid


def build_report_dict(doc, source_path):
    """Build the complete metrics report for a FreeCAD document."""
    report = {
        "schema_version": 4,
        "source": {
            "path": source_path,
            "document_name": doc.Name,
            "document_label": getattr(doc, "Label", doc.Name),
            "freecad_version": get_freecad_version_string(),
            "data_creation_date": datetime.datetime.utcnow().isoformat() + "Z",
            "platform": platform.platform(),
            "python_version": platform.python_version(),
        },
    }

    for obj in _find_final_solid_objects(doc):
        report.setdefault("solids", []).append(evaluate_shape(obj))

    for obj in doc.Objects:
        for section_name, analyzer_fn in ANALYZERS:
            result = analyzer_fn(obj)
            if result is None:
                continue
            report.setdefault(section_name, []).append(result)

    report["invalid_shapes"] = scan_invalid_shapes(doc)

    return report


def parse_args(argv):
    """Parse command-line arguments, or read from EVALUATE_FCSTD/EVALUATE_OUT env vars.

    Env-var mode is used by callers that cannot reliably pass non-ASCII paths via
    the Windows command line (FreeCADCmd's argv parsing mangles UTF-8 in the
    presence of spaces). When EVALUATE_FCSTD is set we skip argparse entirely.
    """
    env_fcstd = os.environ.get("EVALUATE_FCSTD")
    if env_fcstd:
        ns = argparse.Namespace()
        ns.fcstd = env_fcstd
        ns.out = os.environ.get("EVALUATE_OUT")
        return ns

    parser = argparse.ArgumentParser(
        prog=os.path.basename(argv[1]),
        description="Compute per-object metrics from an FCStd file (Python 2 compatible).",
    )
    parser.add_argument("fcstd", help="Path to .FCStd file")
    parser.add_argument(
        "--out", "-o", default=None, help="Write JSON to this file instead of stdout"
    )
    return parser.parse_args(argv[2:])


def main(argv):
    """Open an FCStd file, force recompute, and write a JSON metrics report."""
    args = parse_args(argv)

    fcstd_path = os.path.abspath(args.fcstd)
    if not os.path.isfile(fcstd_path):
        raise SystemExit("Input file not found: " + fcstd_path)

    doc = App.openDocument(fcstd_path)
    # Exit non-zero on a soft open failure so the harness counts it as an error, not a false
    # geometry mismatch from grading an empty report.  FreeCADCmd swallows SystemExit's message,
    # so write the reason to stderr explicitly for the harness to surface.
    if doc is None or not doc.Objects:
        sys.stderr.write("Document opened with no objects (load failed): " + fcstd_path + "\n")
        raise SystemExit(1)
    for obj in doc.Objects:
        try:
            obj.touch()
        except Exception:
            pass
    try:
        doc.recompute()
    except Exception:
        pass

    report = build_report_dict(doc, fcstd_path)

    # Explicit separators: Python 2's json defaults to ", " as the item
    # separator, which leaves trailing whitespace on every line when indent is
    # set.  Matching Python 3's indent-mode default keeps the output clean and
    # identical to EvaluateFile.FCMacro.
    json_text = json.dumps(report, indent=2, sort_keys=True, separators=(",", ": "))

    if args.out:
        out_path = os.path.abspath(args.out)
        with open(out_path, "w") as f:
            f.write(json_text)
            f.write("\n")
    else:
        print(json_text)

    try:
        App.closeDocument(doc.Name)
    except Exception:
        pass


if __name__ == "__main__":
    main(sys.argv)
