#!/usr/bin/env python3
#
# Usage:
#   freecadcmd EvaluateFile.FCMacro /path/to/model.FCStd
#   freecadcmd EvaluateFile.FCMacro /path/to/model.FCStd --out results.json
#
# Outputs a JSON report with per-object metrics, organized by analyzer section.
# Each analyzer handles a specific category of FreeCAD objects (solids, sketches, etc.)
# and multiple analyzers can contribute metrics for the same object.

import datetime
import platform
import sys
import os
import json
import argparse
from typing import Optional

import FreeCAD as App


def is_obj_valid(obj) -> bool:
    """Check whether a FreeCAD document object is valid.

    Falls back to True on older FreeCAD versions (< 0.19) where
    DocumentObject.isValid() does not exist.  Use this for gate checks
    (should we analyze this object?) where "unknown" should mean "try it."

    Args:
        obj: A FreeCAD document object.

    Returns:
        True if the object is valid or if validity cannot be determined.
    """
    try:
        return obj.isValid()
    except AttributeError:
        return True


def report_obj_valid(obj) -> Optional[bool]:
    """Report whether a FreeCAD document object is valid, for recording as a metric.

    Returns None on older FreeCAD versions (< 0.19) where
    DocumentObject.isValid() does not exist, so the comparison logic
    can distinguish "unknown" from a definite True/False.

    Args:
        obj: A FreeCAD document object.

    Returns:
        True/False if the object reports validity, or None if the API is unavailable.
    """
    # An object that did not recompute cleanly (still touched, or in error) is
    # reported as invalid regardless of what isValid() says, because its shape
    # is stale on-disk geometry rather than a recompute result.
    if not recompute_clean(obj):
        return False
    try:
        return obj.isValid()
    except AttributeError:
        return None


def is_shape_valid(shape) -> bool:
    """Check whether a FreeCAD shape is non-null and geometrically valid.

    Args:
        shape: A FreeCAD Part.Shape (or subclass) instance.

    Returns:
        True if the shape is not None, not null, and passes OCC validity checks.
        Returns False on any exception.
    """
    try:
        return (shape is not None) and (not shape.isNull()) and shape.isValid()
    except Exception:
        return False


# Construction/datum object types carry no measured solid geometry.  They are
# frequently left "Invalid" after a load+recompute (App::Origin especially)
# without affecting the solids we measure, so they must NOT count as a recompute
# failure when judging whether a shape is trustworthy.
_CONSTRUCTION_TYPE_IDS = frozenset(
    [
        "App::Origin",
        "App::Line",
        "App::Plane",
        "App::Axis",
        "App::OriginFeature",
        "PartDesign::CoordinateSystem",
        "PartDesign::Plane",
        "PartDesign::Line",
        "PartDesign::Point",
    ]
)


def _is_construction(obj) -> bool:
    """True if obj is a datum/origin construction object with no measured solid."""
    tid = getattr(obj, "TypeId", "") or ""
    return tid in _CONSTRUCTION_TYPE_IDS or "Datum" in tid or "Origin" in tid


def _object_failed_recompute(obj) -> bool:
    """True if obj's own State shows a real, geometry-relevant recompute failure.

    Construction/datum objects are ignored: an Invalid Origin or local
    coordinate system does not make the solids built in the document stale.
    """
    if _is_construction(obj):
        return False
    try:
        state = list(obj.State)
    except Exception:
        return False
    return ("Invalid" in state) or ("Error" in state)


def recompute_clean(obj) -> bool:
    """Return True if a reported object's shape is a trustworthy recompute result.

    After the macro forces a full recompute, a healthy object's shape is the
    output of that recompute.  But when a geometry feature fails to execute --
    e.g. a pre-1.0 PartDesign feature with no Body raising "Missing container
    body", or a sketch that no longer solves -- modern FreeCAD aborts the
    recompute chain.  The failed feature is marked ``Invalid``/``Error`` and
    every object downstream of it is left ``Touched`` while still exposing the
    geometry that was loaded from the saved file.  Reading that ``Shape`` would
    grade stale on-disk geometry rather than a recompute result.

    To detect this without false positives, walk the object together with its
    transitive dependencies (``OutList`` -- the objects this one is built from).
    If any *geometry-producing* object in that closure failed to recompute, the
    shape is untrustworthy.  Merely ``Touched`` objects with no failed
    dependency (e.g. static ``Part::Feature`` imports, or ``App::Part``
    containers whose only invalid child is an Origin) are trustworthy.

    Args:
        obj: A FreeCAD document object (typically a reported final solid).

    Returns:
        True if the shape can be trusted, False if a real recompute failure in
        the object or its dependency closure makes the shape stale.
    """
    seen = set()
    stack = [obj]
    while stack:
        cur = stack.pop()
        name = getattr(cur, "Name", None)
        if name in seen:
            continue
        seen.add(name)
        if _object_failed_recompute(cur):
            return False
        try:
            stack.extend(list(cur.OutList))
        except Exception:
            pass
    return True


def get_solids_from_shape(shape):
    """Extract all solid sub-shapes from a FreeCAD shape.

    For compounds and compsolids, returns shape.Solids. If the shape itself is
    a single Solid, returns it wrapped in a list. Returns an empty list if no
    solids can be extracted.

    Args:
        shape: A FreeCAD Part.Shape (or subclass) instance.

    Returns:
        A list of Part.Solid objects, possibly empty.
    """
    try:
        solids = list(shape.Solids)
        if solids:
            return solids
    except Exception:
        pass

    try:
        if getattr(shape, "ShapeType", "") == "Solid":
            return [shape]
    except Exception:
        pass

    return []


def get_freecad_version_string():
    """Return a human-readable FreeCAD version string (e.g. "1.2.0 45273 (Git)").

    Returns:
        The version string, or "unknown" if it cannot be determined.
    """
    try:
        v = App.Version()
        return ".".join(v[:3]) + (" " + v[3] if len(v) > 3 else "")
    except Exception:
        return "unknown"


class Analyzer:
    """Base class for non-solid object analyzers.

    Subclasses set ``section`` and implement ``can_handle`` and ``evaluate``.
    ``evaluate`` returns a dict with ``_source_name``, ``_source_label``,
    ``_source_type_id``, and ``metrics``.
    """

    section: str = ""

    def can_handle(self, obj) -> bool:
        raise NotImplementedError

    def evaluate(self, obj) -> dict:
        raise NotImplementedError


def evaluate_shape(obj) -> dict:
    """Compute aggregate solid metrics for an object's shape.

    Returns a dict with _source_name, _source_label, _source_type_id, and metrics.
    """
    result = {
        "_source_name": obj.Name,
        "_source_label": getattr(obj, "Label", obj.Name),
        "_source_type_id": getattr(obj, "TypeId", None),
    }

    # A final solid that did not recompute cleanly is reporting the shape that
    # was loaded from the saved file, not a recomputed result -- treat it as
    # invalid so the comparison flags it instead of silently grading stale
    # on-disk geometry.
    if not recompute_clean(obj):
        result["metrics"] = {"is_valid": False}
        return result

    if not is_obj_valid(obj) or not hasattr(obj, "Shape") or not is_shape_valid(obj.Shape):
        result["metrics"] = {"is_valid": False}
        return result

    shape = obj.Shape
    solids = get_solids_from_shape(shape)
    if not solids:
        result["metrics"] = {"is_valid": False}
        return result

    try:
        valid_solids = [s for s in solids if is_shape_valid(s)]
        total_volume = sum(float(s.Volume) for s in valid_solids)
        metrics = {
            "is_valid": True,
            "solid_count": len(solids),
            "total_volume_mm3": total_volume,
            "total_area_mm2": float(shape.Area),
            "bounding_box": {
                "x_min": float(shape.BoundBox.XMin),
                "y_min": float(shape.BoundBox.YMin),
                "z_min": float(shape.BoundBox.ZMin),
                "x_max": float(shape.BoundBox.XMax),
                "y_max": float(shape.BoundBox.YMax),
                "z_max": float(shape.BoundBox.ZMax),
            },
        }
        # CenterOfMass is not available on Part.Compound; compute from
        # solids as a volume-weighted average when the shape doesn't
        # support it directly.
        try:
            com = shape.CenterOfMass
            metrics["center_of_mass"] = {
                "x": float(com.x),
                "y": float(com.y),
                "z": float(com.z),
            }
        except AttributeError:
            if total_volume > 0 and valid_solids:
                wx = sum(float(s.CenterOfMass.x) * float(s.Volume) for s in valid_solids)
                wy = sum(float(s.CenterOfMass.y) * float(s.Volume) for s in valid_solids)
                wz = sum(float(s.CenterOfMass.z) * float(s.Volume) for s in valid_solids)
                metrics["center_of_mass"] = {
                    "x": wx / total_volume,
                    "y": wy / total_volume,
                    "z": wz / total_volume,
                }
    except Exception:
        metrics = {"is_valid": False}

    result["metrics"] = metrics
    return result


class SketchAnalyzer(Analyzer):
    """Analyzer for Sketcher::SketchObject objects.

    Records validity, constraint count, geometry count, and external-geometry
    count.  Transient solver state (degrees of freedom, fully-constrained) is
    deliberately not recorded -- it is unavailable in old FreeCAD versions and
    not part of the file's persistent geometry.
    """

    section = "sketches"

    def can_handle(self, obj) -> bool:
        return obj.TypeId == "Sketcher::SketchObject"

    def evaluate(self, obj) -> dict:
        try:
            metrics = {
                "is_valid": report_obj_valid(obj),
                "constraint_count": int(getattr(obj, "ConstraintCount", 0)),
                "geometry_count": int(getattr(obj, "GeometryCount", 0)),
            }
            try:
                metrics["external_geometry_count"] = len(obj.ExternalGeometry)
            except Exception:
                metrics["external_geometry_count"] = 0
        except Exception:
            metrics = {"is_valid": False}

        return {
            "_source_name": obj.Name,
            "_source_label": obj.Label,
            "_source_type_id": obj.TypeId,
            "metrics": metrics,
        }


class PartDesignBodyAnalyzer(Analyzer):
    """Analyzer for PartDesign::Body objects.

    Extracts feature count and tip feature info from the body.
    """

    section = "partdesign_bodies"

    def can_handle(self, obj) -> bool:
        return obj.TypeId == "PartDesign::Body"

    def evaluate(self, obj) -> dict:
        try:
            metrics = {"is_valid": report_obj_valid(obj)}

            group = getattr(obj, "Group", [])
            metrics["feature_count"] = len(group)

            tip = getattr(obj, "Tip", None)
            if tip is not None:
                metrics["tip_name"] = tip.Name
                metrics["tip_is_valid"] = report_obj_valid(tip)
            else:
                metrics["tip_name"] = None
                metrics["tip_is_valid"] = False
        except Exception:
            metrics = {"is_valid": False}

        return {
            "_source_name": obj.Name,
            "_source_label": obj.Label,
            "_source_type_id": obj.TypeId,
            "metrics": metrics,
        }


class PartDesignFeatureAnalyzer(Analyzer):
    """Analyzer for individual PartDesign features (Pad, Pocket, Fillet, etc.).

    Extracts shape type for PartDesign features that are not the Body container itself.
    """

    section = "partdesign_features"

    # Construction geometry types that should not be analyzed as features.
    _SKIP_TYPES = {
        "PartDesign::Line",
        "PartDesign::Plane",
        "PartDesign::Point",
        "PartDesign::CoordinateSystem",
        "PartDesign::ShapeBinder",
        "PartDesign::SubShapeBinder",
    }

    def can_handle(self, obj) -> bool:
        return (
            obj.TypeId.startswith("PartDesign::")
            and obj.TypeId != "PartDesign::Body"
            and obj.TypeId not in self._SKIP_TYPES
            and hasattr(obj, "Shape")
        )

    def evaluate(self, obj) -> dict:
        try:
            metrics = {"is_valid": report_obj_valid(obj)}
            shape = getattr(obj, "Shape", None)
            if shape is not None and is_shape_valid(shape):
                metrics["shape_type"] = shape.ShapeType
                # solid_count > 1 is a hard error on FreeCAD <= 1.0; allowed from 1.1 on.
                try:
                    metrics["solid_count"] = len(get_solids_from_shape(shape))
                except Exception:
                    pass
        except Exception:
            metrics = {"is_valid": False}

        return {
            "_source_name": obj.Name,
            "_source_label": obj.Label,
            "_source_type_id": obj.TypeId,
            "metrics": metrics,
        }


class PartFeatureAnalyzer(Analyzer):
    """Analyzer for Part workbench features (Cut, Fuse, Extrusion, primitives, etc.).

    Records validity, shape type, shell closure, total volume / area, bounding
    box, center of mass, and the shape's Placement.Base. The geometric metrics
    let the test suite catch regressions like FreeCAD issue #29733
    (`transformShape()` no longer bakes the transform in 1.2-dev), where the
    visible position is unchanged but the shape's internal coordinates and
    Placement diverge between versions. `placement_base` is the field that
    catches that specific failure mode.
    """

    section = "part_features"

    def can_handle(self, obj) -> bool:
        return obj.TypeId.startswith("Part::") and hasattr(obj, "Shape")

    def evaluate(self, obj) -> dict:
        try:
            metrics = {"is_valid": report_obj_valid(obj)}
            shape = getattr(obj, "Shape", None)
            if shape is not None and is_shape_valid(shape):
                metrics["shape_type"] = shape.ShapeType
                try:
                    shells = shape.Shells
                    if shells:
                        metrics["shell_is_closed"] = all(shell.isClosed() for shell in shells)
                except Exception:
                    pass
                # Placement.Base catches transformShape-style regressions where the
                # visible position is unchanged but coordinates vs Placement shift.
                try:
                    base = shape.Placement.Base
                    metrics["placement_base"] = {
                        "x": float(base.x),
                        "y": float(base.y),
                        "z": float(base.z),
                    }
                except Exception:
                    pass
                # Geometric metrics matching the SolidAnalyzer set, where applicable.
                try:
                    metrics["bounding_box"] = {
                        "x_min": float(shape.BoundBox.XMin),
                        "y_min": float(shape.BoundBox.YMin),
                        "z_min": float(shape.BoundBox.ZMin),
                        "x_max": float(shape.BoundBox.XMax),
                        "y_max": float(shape.BoundBox.YMax),
                        "z_max": float(shape.BoundBox.ZMax),
                    }
                except Exception:
                    pass
                try:
                    metrics["total_area_mm2"] = float(shape.Area)
                except Exception:
                    pass
                try:
                    solids = get_solids_from_shape(shape)
                    valid_solids = [s for s in solids if is_shape_valid(s)]
                    if valid_solids:
                        total_volume = sum(float(s.Volume) for s in valid_solids)
                        metrics["total_volume_mm3"] = total_volume
                        try:
                            com = shape.CenterOfMass
                            metrics["center_of_mass"] = {
                                "x": float(com.x),
                                "y": float(com.y),
                                "z": float(com.z),
                            }
                        except AttributeError:
                            if total_volume > 0:
                                wx = sum(
                                    float(s.CenterOfMass.x) * float(s.Volume) for s in valid_solids
                                )
                                wy = sum(
                                    float(s.CenterOfMass.y) * float(s.Volume) for s in valid_solids
                                )
                                wz = sum(
                                    float(s.CenterOfMass.z) * float(s.Volume) for s in valid_solids
                                )
                                metrics["center_of_mass"] = {
                                    "x": wx / total_volume,
                                    "y": wy / total_volume,
                                    "z": wz / total_volume,
                                }
                except Exception:
                    pass
        except Exception:
            metrics = {"is_valid": False}

        return {
            "_source_name": obj.Name,
            "_source_label": obj.Label,
            "_source_type_id": obj.TypeId,
            "metrics": metrics,
        }


class AppPartAnalyzer(Analyzer):
    """Analyzer for App::Part container objects.

    Extracts child object count and overall bounding box dimensions.
    """

    section = "app_parts"

    def can_handle(self, obj) -> bool:
        return obj.TypeId == "App::Part"

    def evaluate(self, obj) -> dict:
        try:
            metrics = {"is_valid": report_obj_valid(obj)}

            group = getattr(obj, "Group", [])
            metrics["child_count"] = len(group)

            shape = getattr(obj, "Shape", None)
            if shape is not None and is_shape_valid(shape):
                metrics["bounding_box"] = {
                    "x_min": float(shape.BoundBox.XMin),
                    "y_min": float(shape.BoundBox.YMin),
                    "z_min": float(shape.BoundBox.ZMin),
                    "x_max": float(shape.BoundBox.XMax),
                    "y_max": float(shape.BoundBox.YMax),
                    "z_max": float(shape.BoundBox.ZMax),
                }
        except Exception:
            metrics = {"is_valid": False}

        return {
            "_source_name": obj.Name,
            "_source_label": obj.Label,
            "_source_type_id": obj.TypeId,
            "metrics": metrics,
        }


class AssemblyAnalyzer(Analyzer):
    """Analyzer for Assembly::AssemblyObject containers.

    Extracts joint count and joint type distribution from the assembly.
    """

    section = "assemblies"

    def can_handle(self, obj) -> bool:
        return obj.TypeId == "Assembly::AssemblyObject"

    def evaluate(self, obj) -> dict:
        try:
            metrics = {"is_valid": report_obj_valid(obj)}

            group = getattr(obj, "Group", [])
            metrics["child_count"] = len(group)

            joint_types = {}
            for child in group:
                child_group = getattr(child, "Group", [])
                for grandchild in child_group:
                    type_id = getattr(grandchild, "TypeId", "")
                    if "Joint" in type_id:
                        joint_types[type_id] = joint_types.get(type_id, 0) + 1

            metrics["joint_count"] = sum(joint_types.values())
            metrics["joint_types"] = joint_types
        except Exception:
            metrics = {"is_valid": False}

        return {
            "_source_name": obj.Name,
            "_source_label": obj.Label,
            "_source_type_id": obj.TypeId,
            "metrics": metrics,
        }


class TechDrawPageAnalyzer(Analyzer):
    """Analyzer for TechDraw::DrawPage objects.

    Extracts view count, view types, and whether a template is loaded.
    """

    section = "techdraw_pages"

    def can_handle(self, obj) -> bool:
        return obj.TypeId == "TechDraw::DrawPage"

    def evaluate(self, obj) -> dict:
        try:
            metrics = {"is_valid": report_obj_valid(obj)}

            views = getattr(obj, "Views", [])
            metrics["view_count"] = len(views)

            view_types = {}
            for view in views:
                type_id = getattr(view, "TypeId", "unknown")
                view_types[type_id] = view_types.get(type_id, 0) + 1
            metrics["view_types"] = view_types

            template = getattr(obj, "Template", None)
            metrics["template_loaded"] = template is not None

            try:
                if template is not None:
                    metrics["template_name"] = getattr(template, "Template", "")
            except Exception:
                pass
        except Exception:
            metrics = {"is_valid": False}

        return {
            "_source_name": obj.Name,
            "_source_label": obj.Label,
            "_source_type_id": obj.TypeId,
            "metrics": metrics,
        }


class SpreadsheetAnalyzer(Analyzer):
    """Analyzer for Spreadsheet::Sheet objects.

    Extracts cell count and alias-to-value mappings for named cells.
    """

    section = "spreadsheets"

    def can_handle(self, obj) -> bool:
        return obj.TypeId == "Spreadsheet::Sheet"

    def evaluate(self, obj) -> dict:
        try:
            metrics = {"is_valid": report_obj_valid(obj)}

            try:
                used_cells = obj.getUsedCells()
                metrics["cell_count"] = len(used_cells)
            except Exception:
                metrics["cell_count"] = -1

            try:
                aliases = {}
                alias_list = obj.getAliases()
                for alias, address in alias_list:
                    try:
                        value = obj.get(alias)
                        if isinstance(value, float):
                            aliases[alias] = float(value)
                        elif isinstance(value, int):
                            aliases[alias] = int(value)
                        elif isinstance(value, str):
                            aliases[alias] = value
                    except Exception:
                        pass
                if aliases:
                    metrics["aliases"] = aliases
            except Exception:
                pass
        except Exception:
            metrics = {"is_valid": False}

        return {
            "_source_name": obj.Name,
            "_source_label": obj.Label,
            "_source_type_id": obj.TypeId,
            "metrics": metrics,
        }


class LinkAnalyzer(Analyzer):
    """Analyzer for App::Link objects.

    Checks whether the linked object exists and is valid, and whether the
    link's shape matches the linked object's shape type.
    """

    section = "links"

    def can_handle(self, obj) -> bool:
        return obj.TypeId == "App::Link"

    def evaluate(self, obj) -> dict:
        try:
            metrics = {"is_valid": report_obj_valid(obj)}

            linked = getattr(obj, "LinkedObject", None)
            metrics["linked_object_name"] = linked.Name if linked is not None else None
            metrics["linked_object_is_valid"] = (
                report_obj_valid(linked) if linked is not None else False
            )

            shape = getattr(obj, "Shape", None)
            if shape is not None and is_shape_valid(shape):
                metrics["shape_type"] = shape.ShapeType
        except Exception:
            metrics = {"is_valid": False}

        return {
            "_source_name": obj.Name,
            "_source_label": obj.Label,
            "_source_type_id": obj.TypeId,
            "metrics": metrics,
        }


class PartExtrusionAnalyzer(Analyzer):
    """Analyzer for Part::Extrusion and Part::Offset2D objects.

    Extracts extrusion-specific parameters such as direction, lengths, and
    offset values that go beyond the general Part feature topology.
    """

    section = "part_extrusions"

    _handled_types = {"Part::Extrusion", "Part::Offset2D", "Part::Offset3D"}

    def can_handle(self, obj) -> bool:
        return obj.TypeId in self._handled_types

    def evaluate(self, obj) -> dict:
        try:
            metrics = {"is_valid": report_obj_valid(obj)}

            if obj.TypeId == "Part::Extrusion":
                direction = getattr(obj, "Dir", None)
                if direction is not None:
                    metrics["direction"] = {
                        "x": float(direction.x),
                        "y": float(direction.y),
                        "z": float(direction.z),
                    }
                try:
                    metrics["length_forward"] = float(obj.LengthFwd)
                except Exception:
                    pass
                try:
                    metrics["length_reverse"] = float(obj.LengthRev)
                except Exception:
                    pass
                try:
                    metrics["solid"] = bool(obj.Solid)
                except Exception:
                    pass
                try:
                    metrics["symmetric"] = bool(obj.Symmetric)
                except Exception:
                    pass

            elif obj.TypeId in ("Part::Offset2D", "Part::Offset3D"):
                try:
                    metrics["offset_value"] = float(obj.Value)
                except Exception:
                    pass
                try:
                    metrics["fill_type"] = str(obj.Fill)
                except Exception:
                    pass
        except Exception:
            metrics = {"is_valid": False}

        return {
            "_source_name": obj.Name,
            "_source_label": obj.Label,
            "_source_type_id": obj.TypeId,
            "metrics": metrics,
        }


class MaterialAnalyzer(Analyzer):
    """Analyzer for material objects (App::MaterialObjectPython and similar).

    Extracts material name and key physical properties such as density.
    """

    section = "materials"

    def can_handle(self, obj) -> bool:
        type_id = getattr(obj, "TypeId", "")
        return "Material" in type_id or (
            hasattr(obj, "Material") and isinstance(getattr(obj, "Material", None), dict)
        )

    def evaluate(self, obj) -> dict:
        try:
            metrics = {"is_valid": report_obj_valid(obj)}

            material = getattr(obj, "Material", None)
            if isinstance(material, dict):
                if "Name" in material:
                    metrics["material_name"] = str(material["Name"])
                if "Density" in material:
                    try:
                        metrics["density"] = float(material["Density"].split()[0])
                    except Exception:
                        metrics["density_raw"] = str(material["Density"])
                if "YoungsModulus" in material:
                    metrics["youngs_modulus_raw"] = str(material["YoungsModulus"])
                if "PoissonRatio" in material:
                    try:
                        metrics["poisson_ratio"] = float(material["PoissonRatio"])
                    except Exception:
                        pass
        except Exception:
            metrics = {"is_valid": False}

        return {
            "_source_name": obj.Name,
            "_source_label": getattr(obj, "Label", obj.Name),
            "_source_type_id": getattr(obj, "TypeId", "unknown"),
            "metrics": metrics,
        }


# Non-solid analyzers.
ANALYZERS = [
    SketchAnalyzer(),
    PartDesignBodyAnalyzer(),
    PartDesignFeatureAnalyzer(),
    PartFeatureAnalyzer(),
    AppPartAnalyzer(),
    AssemblyAnalyzer(),
    TechDrawPageAnalyzer(),
    SpreadsheetAnalyzer(),
    LinkAnalyzer(),
    PartExtrusionAnalyzer(),
    MaterialAnalyzer(),
]


def _find_final_solid_objects(doc):
    """Return only the top-level shape-producing objects in a document.

    Reports PartDesign::Body and App::Part containers, plus any standalone
    solid-producing objects not inside a Body or Part.  Skips intermediate
    features (Pads, Cuts, etc.) whose shapes are subsumed by their container.
    """
    # Collect names of all objects inside a Body or Part
    owned = set()
    for obj in doc.Objects:
        type_id = getattr(obj, "TypeId", "")
        if type_id in ("PartDesign::Body", "App::Part"):
            for child in getattr(obj, "Group", []):
                owned.add(child.Name)
                # Bodies inside Parts: mark body's children too
                if getattr(child, "TypeId", "") == "PartDesign::Body":
                    for grandchild in getattr(child, "Group", []):
                        owned.add(grandchild.Name)

    # Also find objects consumed by other shape-producing objects (for files
    # that use standalone Part features without Body/Part containers)
    consumed = set()
    for obj in doc.Objects:
        if not hasattr(obj, "Shape"):
            continue
        for dep in obj.OutList:
            if hasattr(dep, "Shape"):
                consumed.add(dep.Name)

    skip_types = {
        "PartDesign::Line",
        "PartDesign::Plane",
        "PartDesign::Point",
        "PartDesign::CoordinateSystem",
        "PartDesign::ShapeBinder",
        "PartDesign::SubShapeBinder",
        "Sketcher::SketchObject",
        "App::Origin",
        "App::Line",
        "App::Plane",
        "App::DocumentObjectGroup",
    }

    finals = []
    for obj in doc.Objects:
        type_id = getattr(obj, "TypeId", "")

        if not hasattr(obj, "Shape"):
            continue
        if type_id in skip_types:
            continue

        # Always include Bodies and Parts
        if type_id in ("PartDesign::Body", "App::Part"):
            finals.append(obj)
            continue

        # Skip anything owned by a Body or Part
        if obj.Name in owned:
            continue

        # Skip standalone features consumed by another shape-producing object
        if obj.Name in consumed:
            continue

        # Include if it has solids (or is invalid)
        shape = obj.Shape
        if not is_obj_valid(obj) or not is_shape_valid(shape):
            finals.append(obj)
            continue
        if shape.ShapeType in ("Vertex", "Edge", "Wire", "Face"):
            continue
        if get_solids_from_shape(shape):
            finals.append(obj)

    return finals


def detect_dag_cycles(doc) -> list:
    """Find dependency-graph cycles among the document's objects.

    Builds the adjacency list from `obj.OutList` (the set of objects this
    object depends on) and runs Tarjan's strongly-connected-components
    algorithm. Any SCC of size > 1, or a self-edge SCC of size 1, is a cycle.

    Returns a list of cycles, each cycle being a list of object names in the
    order Tarjan emitted them. Empty list means the graph is a proper DAG.
    A cyclic dependency graph is the most common explanation for
    non-deterministic recompute results, since the topological order of
    recomputation is not well defined.
    """
    graph = {}
    for obj in doc.Objects:
        deps = []
        try:
            for dep in obj.OutList:
                name = getattr(dep, "Name", None)
                if name:
                    deps.append(name)
        except Exception:
            pass
        graph[obj.Name] = deps

    index_counter = [0]
    index_of = {}
    lowlink = {}
    on_stack = {}
    stack = []
    cycles = []

    # Iterative Tarjan to avoid recursion limits on large documents.
    def strongconnect(start):
        work = [(start, 0)]
        call_stack = []
        while work:
            v, i = work[-1]
            if i == 0:
                index_of[v] = index_counter[0]
                lowlink[v] = index_counter[0]
                index_counter[0] += 1
                stack.append(v)
                on_stack[v] = True
            successors = graph.get(v, [])
            if i < len(successors):
                w = successors[i]
                work[-1] = (v, i + 1)
                if w not in index_of:
                    work.append((w, 0))
                elif on_stack.get(w):
                    lowlink[v] = min(lowlink[v], index_of[w])
            else:
                if lowlink[v] == index_of[v]:
                    scc = []
                    while True:
                        w = stack.pop()
                        on_stack[w] = False
                        scc.append(w)
                        if w == v:
                            break
                    if len(scc) > 1 or v in graph.get(v, []):
                        cycles.append(scc)
                work.pop()
                if work:
                    parent = work[-1][0]
                    lowlink[parent] = min(lowlink[parent], lowlink[v])

    for node in graph:
        if node not in index_of:
            strongconnect(node)

    return cycles


def scan_invalid_shapes(doc) -> list:
    """Scan every object for a geometrically invalid BRep Shape (OCCT BRepCheck).

    This catches latent invalid geometry that a file's native FreeCAD version tolerates but
    stricter later versions reject.  Unlike the per-section ``is_valid`` (which grades only final
    solids), this walks EVERY object: a defective intermediate feature (e.g. a Sweep consumed by
    a Cut) can be ``shape.isValid()`` False while every final solid, ``obj.isValid()`` and the
    recompute all report valid.  Reported as a top-level list; the comparison harness ignores
    top-level keys, so this does not affect baselines or pass/fail of the running suite.

    Returns:
        A list of dicts (one per invalid object) with name, label, type_id and obj_valid.
    """
    invalid = []
    for obj in doc.Objects:
        shape = getattr(obj, "Shape", None)
        if shape is None:
            continue
        try:
            if shape.isNull() or shape.isValid():
                continue
        except Exception:
            continue
        try:
            obj_valid = obj.isValid()
        except Exception:
            obj_valid = None
        invalid.append(
            {
                "name": obj.Name,
                "label": getattr(obj, "Label", obj.Name),
                "type_id": obj.TypeId,
                "obj_valid": obj_valid,
            }
        )
    return invalid


def build_report_dict(doc, source_path: str) -> dict:
    """Build the complete metrics report for a FreeCAD document.

    For solid geometry, only final shapes are reported (Body tips, Part
    containers, standalone features).  Non-solid analyzers (sketches,
    assemblies, etc.) run on all matching objects as before.

    Args:
        doc: An open FreeCAD document (App.Document).
        source_path: The filesystem path to the .FCStd file, stored in the report for provenance.

    Returns:
        A dictionary containing "schema_version", "source" metadata, and one key per analyzer
        section (e.g. "solids", "sketches") mapping object names to their metric entries.
    """
    report = {
        "schema_version": 4,
        "source": {
            "path": source_path,
            "document_name": doc.Name,
            "document_label": getattr(doc, "Label", doc.Name),
            "freecad_version": get_freecad_version_string(),
            "data_creation_date": datetime.datetime.now(datetime.timezone.utc).isoformat(),
            "platform": platform.platform(),
            "python_version": platform.python_version(),
        },
        "dag_cycles": detect_dag_cycles(doc),
    }

    # Solid geometry: only final shapes
    for obj in _find_final_solid_objects(doc):
        report.setdefault("solids", []).append(evaluate_shape(obj))

    # Non-solid analyzers: run on all matching objects
    for obj in doc.Objects:
        for analyzer in ANALYZERS:
            if analyzer.can_handle(obj):
                report.setdefault(analyzer.section, []).append(analyzer.evaluate(obj))

    # All-object BRep validity scan (final-solids is_valid does not cover intermediates).
    report["invalid_shapes"] = scan_invalid_shapes(doc)

    return report


def parse_args(argv):
    """Parse command-line arguments for the macro.

    Supports two invocation styles:

    1. **Command-line arguments** (traditional): FreeCADCmd passes the FCStd path and options
       starting at argv[2] (argv[0] is FreeCADCmd, argv[1] is this script).

    2. **Environment variables**: When FreeCADCmd consumes positional arguments before the macro
       can see them (e.g. when launched via ``pixi run``), set ``EVALUATE_FCSTD`` and optionally
       ``EVALUATE_OUT`` instead.  Environment variables take precedence when ``EVALUATE_FCSTD``
       is set.

    Args:
        argv: The full sys.argv list, where argv[0] is the FreeCADCmd executable and argv[1] is
            this script's path.

    Returns:
        An argparse.Namespace with ``fcstd`` (path to .FCStd file) and ``out`` (optional output
        file path, or None for stdout).
    """
    env_fcstd = os.environ.get("EVALUATE_FCSTD")
    if env_fcstd:
        ns = argparse.Namespace()
        ns.fcstd = env_fcstd
        ns.out = os.environ.get("EVALUATE_OUT")
        return ns

    parser = argparse.ArgumentParser(
        prog=os.path.basename(argv[1]),
        description="Compute per-object metrics from an FCStd file and output JSON.",
    )
    parser.add_argument("fcstd", help="Path to .FCStd file")
    parser.add_argument(
        "--out", "-o", default=None, help="Write JSON to this file instead of stdout"
    )
    return parser.parse_args(argv[2:])


def main(argv):
    """Open an FCStd file, force a full recompute, and write a JSON metrics report.

    Marks every object as dirty via touch(), recomputes the document, then runs all registered
    analyzers to produce a metrics report.

    Args:
        argv: The full sys.argv list (see parse_args for format).
    """
    args = parse_args(argv)

    fcstd_path = os.path.abspath(args.fcstd)
    if not os.path.isfile(fcstd_path):
        raise SystemExit(f"Input file not found: {fcstd_path}")

    doc = App.openDocument(fcstd_path)
    # Exit non-zero on a soft open failure so the harness counts it as an error, not a false
    # geometry mismatch from grading an empty report.  FreeCADCmd swallows SystemExit's message,
    # so write the reason to stderr explicitly for the harness to surface.
    if doc is None or not doc.Objects:
        sys.stderr.write(f"Document opened with no objects (load failed): {fcstd_path}\n")
        raise SystemExit(1)
    for obj in doc.Objects:
        try:
            obj.touch()
        except Exception:
            pass
    try:
        doc.recompute()
    except Exception:
        pass

    report = build_report_dict(doc, fcstd_path)

    json_text = json.dumps(report, indent=2, sort_keys=True)

    if args.out:
        out_path = os.path.abspath(args.out)
        with open(out_path, "w", encoding="utf-8") as f:
            f.write(json_text)
            f.write("\n")
    else:
        print(json_text)

    try:
        App.closeDocument(doc.Name)
    except Exception:
        pass


if __name__ == "__main__":
    main(sys.argv)
